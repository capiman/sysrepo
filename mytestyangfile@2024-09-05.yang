module mytestmodule {
  namespace "http://mytestnamespace.notusedtestdomain.de/";
  prefix mytestprefix;
  container mytestcontainer {
    leaf mytestleaf1 {
      type string;
      default "this-is-content-of-leaf-1";
    }
    leaf mytestleaf2 {
      type string;
      default "this-is-content-of-leaf-2";
    }
  }
  container mysecondtestcontainer {
    leaf mytestleaf3 {
      type string;
      default "this-is-content-of-leaf-3";
    }
    leaf mytestleaf4 {
      type string;
      default "this-is-content-of-leaf-4";
    }
  }
}
